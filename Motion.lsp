;=========================================================
(defun c:poweron ( / )
	(while(and (setq key (cadr (grread))) (/= 13 key))
	(cond ((= key 49)(po))
		  ((= key 50)(po2))
		  (t(po3))
	)
	)
)
;=========================================================
(defun po(/ xi yi value_set value e1 e2 up1 up2 up3)
  (command "ucs" "W")
  (command "ucs" "O" '(0 0 20))
  (setq up1 '(-90 -8 10)
  		up2 '(90 -8 10)
		up3 '(-90 -8 20)
  )
  (command "ucs" "3p" up1 up2 up3)
  (command "rectangle" '(0 0 1) '(180 115 1)) (command "extrude" (entlast) "" -100 "") (setq e1 (entlast))
  (command "subtract" e0 "" e1 "") 
  (command "-image" "attach" "apple" '(0 0) 183 0)
)
;===========================================================
(defun po2 (/)
  (command "delay" 3000)
  (command "erase" "l" "")
  (command "-image" "attach" "desktopforcad" '(0 0) 9.2 0)
)
;===========================================================
(defun po3(/)
  (command "erase" "l" "")
  (command "-image" "attach" "caddown" '(0 0) 8.1 0)
  (command "-image" "attach" "cadtop" '(0 95) 8.1 0)
)
;============================================================
(defun c:kbon(/ e1 e2 e3 ce cm lencm xi yi value_set value up1 up2 up3 tp1 fo)
  (command "ucs" "W")
  (setq ;ce 0 
  		cm (list) e1 (entlast)) 
  (command "ucs" "O" '(0 0 20))
  (setq up1 '(-90 -8 10)
  		up2 '(90 -8 10)
      	up3 '(-90 -8 20)
  )
  (command "ucs" "3p" up1 up2 up3)
  (setq tp1 '(0 10))
  (command "ucs" "W")
  (while (and (setq key (cadr (grread))) (/= 13 key)) 
	(setq xi (nth 0 key) 
		  yi (nth 1 key)
	)
    (setq value_set (finddat2 "auto_key_coordinate.dat" xi yi))
;    (setq value_set (finddat2 (findfile "key_coordinate.dat") xi yi))
    (setq value (nth 4 value_set))
    (command "ucs" "O" '(0 0 20))
    (setq up1 '(-90 -8 10)
    		up2 '(90 -8 10)
        	up3 '(-90 -8 20)
    )
    (command "ucs" "3p" up1 up2 up3)
	(command "text" tp1 "3" "0" value)
    (princ value)
	(princ " ")
	(setq tp1 (rpoint tp1 3 0))
	(command "ucs" "w")
	(setq cm (cons value cm))
;	(if (= value " ") (setq ce (+ 1 ce))
;	(cond (= ce 0) (setq cm (cons value cm))
;		  (= ce 1) (setq p1 (cons value p1))
;		  (= ce 2) (setq p2 (cons value p2))
;	)
;	)
  )
  (setq e2 (entlast)
  		e3 (sset e1 e2)
  )
  (command "-vpoint" '(0 -100 0))
  (command "zoom" "e")
  (setq cm (reverse cm)) 
  (princ cm)
;  (princ p1)
;  (princ p2)
  (setq i 0 lencm (length cm)) 
  (setq c1 (apply 'strcat cm))
  (command "ucs" "O" '(0 0 20))
  (command "ucs" "3p" up1 up2 up3)
  (command c1)
  (command "erase" e3 "")
;  (setq i 0)
;  (command 
;  (while (< i (length p1))
;  (nth i p1)))
;  (setq i 0)
;  (command 
;  (while (< i (length p2))
;  (nth i p2)))

)
;==========================================
